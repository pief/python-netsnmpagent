SIMPLE-MIB DEFINITIONS ::= BEGIN

------------------------------------------------------------------------
-- Simple example MIB for python-netsnmpagent
-- Copyright (c) 2012-2019 Pieter Hollants <pieter@hollants.com>
-- Licensed under the GNU Lesser Public License (LGPL) version 3
------------------------------------------------------------------------

-- Imports
IMPORTS
    MODULE-IDENTITY, OBJECT-TYPE, NOTIFICATION-TYPE,
    Integer32, Unsigned32, Counter32, Counter64, TimeTicks, IpAddress,
    enterprises
        FROM SNMPv2-SMI
    TEXTUAL-CONVENTION, DisplayString
        FROM SNMPv2-TC
    MODULE-COMPLIANCE, OBJECT-GROUP, NOTIFICATION-GROUP
        FROM SNMPv2-CONF
    agentxObjects
        FROM AGENTX-MIB;

-- Description and update information
simpleMIB MODULE-IDENTITY
    LAST-UPDATED "201307070000Z"
    ORGANIZATION "N/A"
    CONTACT-INFO
        "Editor:
        Pieter Hollants
        EMail: <pieter@hollants.com>"
    DESCRIPTION
        "Simple example MIB for python-netsnmpagent"

    REVISION    "201307070000Z"
    DESCRIPTION
        "A simple example MIB for python-netsnmpagent's simple.py."

    ::= { agentxObjects 30187 }

-- Definition of a generic SimpleNotificationStatus type
SimpleNotificationStatus ::= TEXTUAL-CONVENTION
    STATUS current
    DESCRIPTION
        "Indicates the enabling or disabling of a particular class of
        notifications."
    SYNTAX INTEGER {
        disabled (0),   -- This class of notifications is disabled
        enabled  (1)    -- This class of notifications is enabled
}

-- Definition of MIB's root nodes

simpleMIBObjects         OBJECT IDENTIFIER ::= { simpleMIB 1 }
simpleMIBNotifications   OBJECT IDENTIFIER ::= { simpleMIB 2 }
simpleMIBConformance     OBJECT IDENTIFIER ::= { simpleMIB 3 }

simpleScalars            OBJECT IDENTIFIER ::= { simpleMIBObjects 1 }
simpleTables             OBJECT IDENTIFIER ::= { simpleMIBObjects 2 }

------------------------------------------------------------------------
-- Scalars
------------------------------------------------------------------------

simpleUnsigned OBJECT-TYPE
    SYNTAX      Unsigned32
    MAX-ACCESS  read-write
    STATUS      current
    DESCRIPTION
        "A read-write, unsigned, 32-bits integer value."
    ::= { simpleScalars 1 }

simpleUnsignedRO OBJECT-TYPE
    SYNTAX      Unsigned32
    MAX-ACCESS  read-only
    STATUS      current
    DESCRIPTION
        "A read-only, unsigned, 32-bits integer value."
    ::= { simpleScalars 2 }

simpleInteger OBJECT-TYPE
    SYNTAX      Integer32
    MAX-ACCESS  read-write
    STATUS      current
    DESCRIPTION
        "A read-write, signed, 32-bits integer value."
    ::= { simpleScalars 3 }

simpleIntegerRO OBJECT-TYPE
    SYNTAX      Integer32
    MAX-ACCESS  read-only
    STATUS      current
    DESCRIPTION
        "A read-only, signed, 32-bits integer value."
    ::= { simpleScalars 4 }

simpleCounter32 OBJECT-TYPE
    SYNTAX      Counter32
    MAX-ACCESS  read-only
    STATUS      current
    DESCRIPTION
        "A read-only, unsigned, 32-bits counter value."
    ::= { simpleScalars 5 }

simpleCounter64 OBJECT-TYPE
    SYNTAX      Counter64
    MAX-ACCESS  read-only
    STATUS      current
    DESCRIPTION
        "A read-only, unsigned, 64-bits counter value."
    ::= { simpleScalars 6 }

simpleTimeTicks OBJECT-TYPE
    SYNTAX      TimeTicks
    MAX-ACCESS  read-write
    STATUS      current
    DESCRIPTION
        "A read-only, unsigned, 32-bits TimeTicks value."
    ::= { simpleScalars 7 }

simpleIpAddress OBJECT-TYPE
    SYNTAX      IpAddress
    MAX-ACCESS  read-write
    STATUS      current
    DESCRIPTION
        "A 32-bits IPv4 address."
    ::= { simpleScalars 8 }

simpleFloat OBJECT-TYPE
    SYNTAX      Float
    MAX-ACCESS  read-write
    STATUS      current
    DESCRIPTION
        "An opaque-encoded float value."
    ::= { simpleScalars 9 }

SimpleOctetString ::= TEXTUAL-CONVENTION
    DISPLAY-HINT    "1024t"
    STATUS          current
    DESCRIPTION
        "An octet string containing characters in UTF-8 encoding."
    SYNTAX          OCTET STRING (SIZE (1..1024))

simpleOctetString OBJECT-TYPE
    SYNTAX      SimpleOctetString
    MAX-ACCESS  read-only
    STATUS      current
    DESCRIPTION
        "An UTF-8 encoded string value."
    ::= { simpleScalars 10 }

simpleDisplayString OBJECT-TYPE
    SYNTAX      DisplayString
    MAX-ACCESS  read-only
    STATUS      current
    DESCRIPTION
        "An ASCII string value."
    ::= { simpleScalars 11 }

SimpleEnumVal ::= TEXTUAL-CONVENTION
    STATUS          current
    DESCRIPTION
        "A EnumValue"
    SYNTAX          Integer32 { Release(0), Debue(1), Testing(2), Stable(3) }

simpleEnumVal OBJECT-TYPE
    SYNTAX      SimpleEnumVal
    MAX-ACCESS  read-only
    STATUS      current
    DESCRIPTION
        "An ASCII string value."
    ::= { simpleScalars 12 }

------------------------------------------------------------------------
-- Tables
------------------------------------------------------------------------

firstTableNumber OBJECT-TYPE
    SYNTAX      Unsigned32
    MAX-ACCESS  read-only
    STATUS      current
    DESCRIPTION
        "The number of rows in firstTable."
    ::= { simpleTables 1 }

firstTable OBJECT-TYPE
    SYNTAX      SEQUENCE OF FirstTableRow
    MAX-ACCESS  not-accessible
    STATUS      current
    DESCRIPTION
        "The first simple table"
    ::= { simpleTables 2 }

firstTableRow OBJECT-TYPE
    SYNTAX      FirstTableRow
    MAX-ACCESS  not-accessible
    STATUS      current
    DESCRIPTION
        "A particular firstTable row."
    INDEX { firstTableRowIndex }
    ::= { firstTable 1 }

FirstTableRow ::=
    SEQUENCE {
        firstTableRowIndex  DisplayString,
        firstTableRowDesc   DisplayString,
        firstTableRowValue  Integer32
    }

firstTableRowIndex OBJECT-TYPE
    SYNTAX      DisplayString
    MAX-ACCESS  not-accessible
    STATUS      current
    DESCRIPTION
        "The index column used to generate string indices into
        firstTable."
    ::= { firstTableRow 1 }

firstTableRowDesc OBJECT-TYPE
    SYNTAX      DisplayString
    MAX-ACCESS  read-only
    STATUS      current
    DESCRIPTION
        "A firstTableRow's description."
    ::= { firstTableRow 2 }

firstTableRowValue OBJECT-TYPE
    SYNTAX      Integer32
    MAX-ACCESS  read-only
    STATUS      current
    DESCRIPTION
        "A firstTableRow's value."
    ::= { firstTableRow 3 }

firstTableEnumVale OBJECT-TYPE
    SYNTAX      SimpleEnumVal
    MAX-ACCESS  read-only
    STATUS      current
    DESCRIPTION
        "A firstTableEnumVale's value."
    ::= { firstTableRow 4 }

secondTableNumber OBJECT-TYPE
    SYNTAX      Unsigned32
    MAX-ACCESS  read-only
    STATUS      current
    DESCRIPTION
        "The number of rows in secondTable."
    ::= { simpleTables 3 }

secondTable OBJECT-TYPE
    SYNTAX      SEQUENCE OF SecondTableRow
    MAX-ACCESS  not-accessible
    STATUS      current
    DESCRIPTION
        "The second simple table"
    ::= { simpleTables 4 }

secondTableRow OBJECT-TYPE
    SYNTAX      SecondTableRow
    MAX-ACCESS  not-accessible
    STATUS      current
    DESCRIPTION
        "A particular secondTable row."
    INDEX { secondTableRowIndex }
    ::= { secondTable 1 }

SecondTableRow ::=
    SEQUENCE {
        secondTableRowIndex  Integer32,
        secondTableRowDesc   DisplayString,
        secondTableRowValue  Unsigned32
    }

secondTableRowIndex OBJECT-TYPE
    SYNTAX      Integer32 (0..2147483647)
    MAX-ACCESS  not-accessible
    STATUS      current
    DESCRIPTION
        "The index column used to generate numerical indices into
        secondTable."
    ::= { secondTableRow 1 }

secondTableRowDesc OBJECT-TYPE
    SYNTAX      DisplayString
    MAX-ACCESS  read-only
    STATUS      current
    DESCRIPTION
        "An secondTableRow's description."
    ::= { secondTableRow 2 }

secondTableRowValue OBJECT-TYPE
    SYNTAX      Unsigned32
    MAX-ACCESS  read-only
    STATUS      current
    DESCRIPTION
        "An secondTableRow's value."
    ::= { secondTableRow 3 }

thirdTableNumber OBJECT-TYPE
    SYNTAX      Unsigned32
    MAX-ACCESS  read-only
    STATUS      current
    DESCRIPTION
        "The number of rows in thirdTable."
    ::= { simpleTables 5 }

thirdTable OBJECT-TYPE
    SYNTAX      SEQUENCE OF ThirdTableRow
    MAX-ACCESS  not-accessible
    STATUS      current
    DESCRIPTION
        "The third simple table"
    ::= { simpleTables 6 }

thirdTableRow OBJECT-TYPE
    SYNTAX      ThirdTableRow
    MAX-ACCESS  not-accessible
    STATUS      current
    DESCRIPTION
        "A particular thirdTable row."
    INDEX { thirdTableRowIndex }
    ::= { thirdTable 1 }

ThirdTableRow ::=
    SEQUENCE {
        thirdTableRowIndex  IpAddress,
        thirdTableRowDesc   DisplayString,
        thirdTableRowValue  IpAddress
    }

thirdTableRowIndex OBJECT-TYPE
    SYNTAX      IpAddress
    MAX-ACCESS  not-accessible
    STATUS      current
    DESCRIPTION
        "The index column used to generate IpAddress indices into
        thirdTable."
    ::= { thirdTableRow 1 }

thirdTableRowDesc OBJECT-TYPE
    SYNTAX      DisplayString
    MAX-ACCESS  read-only
    STATUS      current
    DESCRIPTION
        "A thirdTableRow's description."
    ::= { thirdTableRow 2 }

thirdTableRowValue OBJECT-TYPE
    SYNTAX      IpAddress
    MAX-ACCESS  read-only
    STATUS      current
    DESCRIPTION
        "A thirdTableRow's value."
    ::= { thirdTableRow 3 }

fourthTableNumber OBJECT-TYPE
    SYNTAX      Unsigned32
    MAX-ACCESS  read-only
    STATUS      current
    DESCRIPTION
        "The number of rows in fourthTable."
    ::= { simpleTables 7 }

fourthTable OBJECT-TYPE
    SYNTAX      SEQUENCE OF FourthTableRow
    MAX-ACCESS  not-accessible
    STATUS      current
    DESCRIPTION
        "The fourth simple table"
    ::= { simpleTables 8 }

fourthTableRow OBJECT-TYPE
    SYNTAX      FourthTableRow
    MAX-ACCESS  not-accessible
    STATUS      current
    DESCRIPTION
        "A particular fourthTable row."
    INDEX { fourthTableRowIndex }
    ::= { fourthTable 1 }

FourthTableRow ::=
    SEQUENCE {
        fourthTableRowIndex  SimpleEnumVal,
        fourthTableRowDesc   DisplayString,
        fourthTableRowValue  IpAddress
    }

fourthTableRowIndex OBJECT-TYPE
    SYNTAX      SimpleEnumVal
    MAX-ACCESS  not-accessible
    STATUS      current
    DESCRIPTION
        "The index column used to generate IpAddress indices into
        fourthTable."
    ::= { fourthTableRow 1 }

fourthTableRowDesc OBJECT-TYPE
    SYNTAX      DisplayString
    MAX-ACCESS  read-only
    STATUS      current
    DESCRIPTION
        "A fourthTableRow's description."
    ::= { fourthTableRow 2 }

fourthTableRowValue OBJECT-TYPE
    SYNTAX      IpAddress
    MAX-ACCESS  read-only
    STATUS      current
    DESCRIPTION
        "A fourthTableRow's value."
    ::= { fourthTableRow 3 }
------------------------------------------------------------------------
-- Notifications
------------------------------------------------------------------------

events      OBJECT IDENTIFIER ::= { simpleMIBNotifications 0 }
operation   OBJECT IDENTIFIER ::= { simpleMIBNotifications 1 }

simpleUnsignedROChange NOTIFICATION-TYPE
    OBJECTS {
        simpleUnsignedRO
    }
    STATUS  current
    DESCRIPTION
        "A simpleScalarsChange notification signifies that there has
        been a change to the value of simpleUnsignedRO."
    ::= { events 1 }

firstTableChange NOTIFICATION-TYPE
    OBJECTS {
        firstTableRowDesc, firstTableRowValue
    }
    STATUS  current
    DESCRIPTION
        "A firstTableChange notification signifies that there has
        been a change to an firstTableRow."
    ::= { events 2 }

simpleUnsignedROChangeNotificationsEnabled OBJECT-TYPE
    SYNTAX      SimpleNotificationStatus
    MAX-ACCESS  read-write
    STATUS      current
    DESCRIPTION
        "Controls whether simpleUnsignedROChange notifications are
        enabled or disabled."
    ::= { operation 1 }

firstTableChangeNotificationsEnabled OBJECT-TYPE
    SYNTAX      SimpleNotificationStatus
    MAX-ACCESS  read-write
    STATUS      current
    DESCRIPTION
        "Controls whether firstTableChange notifications are
        enabled or disabled."
    ::= { operation 2 }

------------------------------------------------------------------------
-- Conformance
------------------------------------------------------------------------

simpleMIBGroups      OBJECT IDENTIFIER ::= { simpleMIBConformance 1 }
simpleMIBCompliances OBJECT IDENTIFIER ::= { simpleMIBConformance 2 }

simpleMIBScalarsGroup OBJECT-GROUP
    OBJECTS {
        simpleInteger, simpleIntegerRO,
        simpleUnsigned, simpleUnsignedRO,
        simpleCounter32, simpleCounter64,
        simpleTimeTicks,
        simpleIpAddress,
        simpleOctetString, simpleDisplayString,
        simpleUnsignedROChangeNotificationsEnabled
    }
    STATUS  current
    DESCRIPTION
        "A collection of objects related to simpleScalars."
    ::= { simpleMIBGroups 1 }

simpleMIBTablesGroup OBJECT-GROUP
    OBJECTS {
        firstTableNumber,
        firstTableRowDesc, firstTableRowValue,
        firstTableChangeNotificationsEnabled,
        secondTableNumber,
        secondTableRowDesc, secondTableRowValue,
        thirdTableNumber,
        thirdTableRowDesc, thirdTableRowValue
    }
    STATUS  current
    DESCRIPTION
        "A collection of objects related to simpleTables."
    ::= { simpleMIBGroups 2 }

simpleMIBScalarsNotificationsGroup NOTIFICATION-GROUP
    NOTIFICATIONS {
        simpleUnsignedROChange
    }
    STATUS  current
    DESCRIPTION
        "The notifications which indicate specific changes in
        simpleMIBScalars."
    ::= { simpleMIBGroups 3 }

simpleMIBTablesNotificationsGroup NOTIFICATION-GROUP
    NOTIFICATIONS {
        firstTableChange
    }
    STATUS  current
    DESCRIPTION
        "The notifications which indicate specific changes in
        simpleTables."
    ::= { simpleMIBGroups 4 }

END
