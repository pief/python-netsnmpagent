TEST-MIB DEFINITIONS ::= BEGIN

------------------------------------------------------------------------
-- MIB for python-netsnmpagent unit tests
-- Copyright (c) 2014-2019 Pieter Hollants <pieter@hollants.com>
-- Licensed under the GNU Lesser Public License (LGPL) version 3
------------------------------------------------------------------------

-- Imports
IMPORTS
    MODULE-IDENTITY, OBJECT-TYPE, NOTIFICATION-TYPE,
    Integer32, Unsigned32, Counter32, Counter64, Gauge32, TimeTicks,
    IpAddress, enterprises
        FROM SNMPv2-SMI
    Float
        FROM NET-SNMP-TC
    TEXTUAL-CONVENTION, DisplayString, TruthValue
        FROM SNMPv2-TC
    MODULE-COMPLIANCE, OBJECT-GROUP, NOTIFICATION-GROUP
        FROM SNMPv2-CONF
    agentxObjects
        FROM AGENTX-MIB;

-- Description and update information
testMIB MODULE-IDENTITY
    LAST-UPDATED "201404190000Z"
    ORGANIZATION "N/A"
    CONTACT-INFO
        "Editor:
        Pieter Hollants
        EMail: <pieter@hollants.com>"
    DESCRIPTION
        "A MIB for python-netsnmpagent unit testing"

    REVISION    "201404190000Z"
    DESCRIPTION
        "First version."

    ::= { agentxObjects 101 }

-- Definition of MIB's root nodes

testMIBObjects  OBJECT IDENTIFIER ::= { testMIB 1 }

testScalars     OBJECT IDENTIFIER ::= { testMIBObjects 1 }

------------------------------------------------------------------------
-- Scalars
------------------------------------------------------------------------

testInteger32      OBJECT IDENTIFIER ::= { testScalars 1 }
testUnsigned32     OBJECT IDENTIFIER ::= { testScalars 2 }
testCounter32      OBJECT IDENTIFIER ::= { testScalars 3 }
testCounter64      OBJECT IDENTIFIER ::= { testScalars 4 }
testGauge32        OBJECT IDENTIFIER ::= { testScalars 5 }
testTimeTicks      OBJECT IDENTIFIER ::= { testScalars 6 }
testIpAddress      OBJECT IDENTIFIER ::= { testScalars 7 }
testTruthValue     OBJECT IDENTIFIER ::= { testScalars 8 }
testFloat          OBJECT IDENTIFIER ::= { testScalars 9 }
testOctetString    OBJECT IDENTIFIER ::= { testScalars 10 }
testDisplayString  OBJECT IDENTIFIER ::= { testScalars 11 }

-- Test OIDs for the Integer32 scalar type
testInteger32NoInitval OBJECT-TYPE
    SYNTAX      Integer32
    MAX-ACCESS  read-write
    STATUS      current
    DESCRIPTION
        "A read-write, signed, 32-bits integer value, with no initval."
    ::= { testInteger32 1 }

testInteger32ZeroInitval OBJECT-TYPE
    SYNTAX      Integer32
    MAX-ACCESS  read-write
    STATUS      current
    DESCRIPTION
        "A read-write, signed, 32-bits integer value, with an initval of
        zero."
    ::= { testInteger32 2 }

testInteger32MinusOneInitval OBJECT-TYPE
    SYNTAX      Integer32
    MAX-ACCESS  read-write
    STATUS      current
    DESCRIPTION
        "A read-write, signed, 32-bits integer value, with an initval of
        minus one."
    ::= { testInteger32 3 }

testInteger32MinInitval OBJECT-TYPE
    SYNTAX      Integer32
    MAX-ACCESS  read-write
    STATUS      current
    DESCRIPTION
        "A read-write, signed, 32-bits integer value, with an initval of
        the minimum allowed value (-2147483648)."
    ::= { testInteger32 4 }

testInteger32MinMinusOneInitval OBJECT-TYPE
    SYNTAX      Integer32
    MAX-ACCESS  read-write
    STATUS      current
    DESCRIPTION
        "A read-write, signed, 32-bits integer value, with an initval of
        the minimum allowed value (-2147483648) minus one."
    ::= { testInteger32 5 }

testInteger32OneInitval OBJECT-TYPE
    SYNTAX      Integer32
    MAX-ACCESS  read-write
    STATUS      current
    DESCRIPTION
        "A read-write, signed, 32-bits integer value, with an initval of
        one."
    ::= { testInteger32 6 }

testInteger32MaxInitval OBJECT-TYPE
    SYNTAX      Integer32
    MAX-ACCESS  read-write
    STATUS      current
    DESCRIPTION
        "A read-write, signed, 32-bits integer value, with an initval of
        the maximum value (2147483647)."
    ::= { testInteger32 7 }

testInteger32MaxPlusOneInitval OBJECT-TYPE
    SYNTAX      Integer32
    MAX-ACCESS  read-write
    STATUS      current
    DESCRIPTION
        "A read-write, signed, 32-bits integer value, with an initval of
        the maximum value (2147483647) plus one."
    ::= { testInteger32 8 }

testInteger32ReadOnly OBJECT-TYPE
    SYNTAX      Integer32
    MAX-ACCESS  read-only
    STATUS      current
    DESCRIPTION
        "A read-only, signed, 32-bits integer value, with no initval."
    ::= { testInteger32 9 }

-- Test OIDs for the Unsigned32 scalar type
testUnsigned32NoInitval OBJECT-TYPE
    SYNTAX      Unsigned32
    MAX-ACCESS  read-write
    STATUS      current
    DESCRIPTION
        "A read-write, unsigned, 32-bits integer value, with no initval."
    ::= { testUnsigned32 1 }

testUnsigned32ZeroInitval OBJECT-TYPE
    SYNTAX      Unsigned32
    MAX-ACCESS  read-write
    STATUS      current
    DESCRIPTION
        "A read-write, unsigned, 32-bits integer value, with an initval of
        zero."
    ::= { testUnsigned32 2 }

testUnsigned32MinusOneInitval OBJECT-TYPE
    SYNTAX      Unsigned32
    MAX-ACCESS  read-write
    STATUS      current
    DESCRIPTION
        "A read-write, unsigned, 32-bits integer value, with an initval of
        minus one."
    ::= { testUnsigned32 3 }

testUnsigned32OneInitval OBJECT-TYPE
    SYNTAX      Unsigned32
    MAX-ACCESS  read-write
    STATUS      current
    DESCRIPTION
        "A read-write, unsigned, 32-bits integer value, with an initval of
        one."
    ::= { testUnsigned32 4 }

testUnsigned32MaxInitval OBJECT-TYPE
    SYNTAX      Unsigned32
    MAX-ACCESS  read-write
    STATUS      current
    DESCRIPTION
        "A read-write, unsigned, 32-bits integer value, with an initval of
        the maximum value (4294967295)."
    ::= { testUnsigned32 5 }

testUnsigned32MaxPlusOneInitval OBJECT-TYPE
    SYNTAX      Unsigned32
    MAX-ACCESS  read-write
    STATUS      current
    DESCRIPTION
        "A read-write, unsigned, 32-bits integer value, with an initval of
        the maximum value (4294967295) plus one."
    ::= { testUnsigned32 6 }

testUnsigned32ReadOnly OBJECT-TYPE
    SYNTAX      Unsigned32
    MAX-ACCESS  read-only
    STATUS      current
    DESCRIPTION
        "A read-only, unsigned, 32-bits integer value, with no initval."
    ::= { testUnsigned32 7 }

-- Test OIDs for the Counter32 scalar type
testCounter32NoInitval OBJECT-TYPE
    SYNTAX      Counter32
    MAX-ACCESS  read-write
    STATUS      current
    DESCRIPTION
        "A read-write, unsigned, 32-bits, monotonically increasing integer
        value, with no initval."
    ::= { testCounter32 1 }

testCounter32ZeroInitval OBJECT-TYPE
    SYNTAX      Counter32
    MAX-ACCESS  read-write
    STATUS      current
    DESCRIPTION
        "A read-write, unsigned, 32-bits, monotonically increasing integer
        value, with an initval of zero."
    ::= { testCounter32 2 }

testCounter32MinusOneInitval OBJECT-TYPE
    SYNTAX      Counter32
    MAX-ACCESS  read-write
    STATUS      current
    DESCRIPTION
        "A read-write, unsigned, 32-bits, monotonically increasing integer
        value, with an initval of minus one."
    ::= { testCounter32 3 }

testCounter32OneInitval OBJECT-TYPE
    SYNTAX      Counter32
    MAX-ACCESS  read-write
    STATUS      current
    DESCRIPTION
        "A read-write, unsigned, 32-bits, monotonically increasing integer
        value, with an initval of one."
    ::= { testCounter32 4 }

testCounter32MaxInitval OBJECT-TYPE
    SYNTAX      Counter32
    MAX-ACCESS  read-write
    STATUS      current
    DESCRIPTION
        "A read-write, unsigned, 32-bits, monotonically increasing integer
        value, with an initval of the maximum value (4294967295)."
    ::= { testCounter32 5 }

testCounter32MaxPlusOneInitval OBJECT-TYPE
    SYNTAX      Counter32
    MAX-ACCESS  read-write
    STATUS      current
    DESCRIPTION
        "A read-write, unsigned, 32-bits, monotonically increasing integer
        value, with an initval of the maximum value (4294967295) plus one."
    ::= { testCounter32 6 }

-- Test OIDs for the Counter64 scalar type
testCounter64NoInitval OBJECT-TYPE
    SYNTAX      Counter64
    MAX-ACCESS  read-write
    STATUS      current
    DESCRIPTION
        "A read-write, unsigned, 64-bits, monotonically increasing integer
        value, with no initval."
    ::= { testCounter64 1 }

testCounter64ZeroInitval OBJECT-TYPE
    SYNTAX      Counter64
    MAX-ACCESS  read-write
    STATUS      current
    DESCRIPTION
        "A read-write, unsigned, 64-bits, monotonically increasing integer
        value, with an initval of zero."
    ::= { testCounter64 2 }

testCounter64MinusOneInitval OBJECT-TYPE
    SYNTAX      Counter64
    MAX-ACCESS  read-write
    STATUS      current
    DESCRIPTION
        "A read-write, unsigned, 64-bits, monotonically increasing integer
        value, with an initval of minus one."
    ::= { testCounter64 3 }

testCounter64OneInitval OBJECT-TYPE
    SYNTAX      Counter64
    MAX-ACCESS  read-write
    STATUS      current
    DESCRIPTION
        "A read-write, unsigned, 64-bits, monotonically increasing integer
        value, with an initval of one."
    ::= { testCounter64 4 }

testCounter64MaxInitval OBJECT-TYPE
    SYNTAX      Counter64
    MAX-ACCESS  read-write
    STATUS      current
    DESCRIPTION
        "A read-write, unsigned, 64-bits, monotonically increasing integer
        value, with an initval of the maximum value (18446744073709551615)."
    ::= { testCounter64 5 }

testCounter64MaxPlusOneInitval OBJECT-TYPE
    SYNTAX      Counter64
    MAX-ACCESS  read-write
    STATUS      current
    DESCRIPTION
        "A read-write, unsigned, 64-bits, monotonically increasing integer
        value, with an initval of the maximum value (18446744073709551615)
        plus one."
    ::= { testCounter64 6 }

-- Test OIDs for the Gauge32 scalar type
testGauge32NoInitval OBJECT-TYPE
    SYNTAX      Gauge32
    MAX-ACCESS  read-write
    STATUS      current
    DESCRIPTION
        "A read-write, unsigned, 32-bits, monotonically increasing integer
        value, with no initval."
    ::= { testGauge32 1 }

testGauge32ZeroInitval OBJECT-TYPE
    SYNTAX      Gauge32
    MAX-ACCESS  read-write
    STATUS      current
    DESCRIPTION
        "A read-write, unsigned, 32-bits, monotonically increasing integer
        value, with an initval of zero."
    ::= { testGauge32 2 }

testGauge32MinusOneInitval OBJECT-TYPE
    SYNTAX      Gauge32
    MAX-ACCESS  read-write
    STATUS      current
    DESCRIPTION
        "A read-write, unsigned, 32-bits, monotonically increasing integer
        value, with an initval of minus one."
    ::= { testGauge32 3 }

testGauge32OneInitval OBJECT-TYPE
    SYNTAX      Gauge32
    MAX-ACCESS  read-write
    STATUS      current
    DESCRIPTION
        "A read-write, unsigned, 32-bits, monotonically increasing integer
        value, with an initval of one."
    ::= { testGauge32 4 }

testGauge32MaxInitval OBJECT-TYPE
    SYNTAX      Gauge32
    MAX-ACCESS  read-write
    STATUS      current
    DESCRIPTION
        "A read-write, unsigned, 32-bits, monotonically increasing integer
        value, with an initval of the maximum value (4294967295)."
    ::= { testGauge32 5 }

testGauge32MaxPlusOneInitval OBJECT-TYPE
    SYNTAX      Gauge32
    MAX-ACCESS  read-write
    STATUS      current
    DESCRIPTION
        "A read-write, unsigned, 32-bits, monotonically increasing integer
        value, with an initval of the maximum value (4294967295) plus one."
    ::= { testGauge32 6 }

-- Test OIDs for the TimeTicks scalar type
testTimeTicksNoInitval OBJECT-TYPE
    SYNTAX      TimeTicks
    MAX-ACCESS  read-write
    STATUS      current
    DESCRIPTION
        "A read-write, unsigned, 32-bits integer value, with no initval."
    ::= { testTimeTicks 1 }

testTimeTicksZeroInitval OBJECT-TYPE
    SYNTAX      TimeTicks
    MAX-ACCESS  read-write
    STATUS      current
    DESCRIPTION
        "A read-write, unsigned, 32-bits integer value, with an initval of
        zero."
    ::= { testTimeTicks 2 }

testTimeTicksMinusOneInitval OBJECT-TYPE
    SYNTAX      TimeTicks
    MAX-ACCESS  read-write
    STATUS      current
    DESCRIPTION
        "A read-write, unsigned, 32-bits integer value, with an initval of
        minus one."
    ::= { testTimeTicks 3 }

testTimeTicksOneInitval OBJECT-TYPE
    SYNTAX      TimeTicks
    MAX-ACCESS  read-write
    STATUS      current
    DESCRIPTION
        "A read-write, unsigned, 32-bits integer value, with an initval of
        one."
    ::= { testTimeTicks 4 }

testTimeTicksMaxInitval OBJECT-TYPE
    SYNTAX      TimeTicks
    MAX-ACCESS  read-write
    STATUS      current
    DESCRIPTION
        "A read-write, unsigned, 32-bits integer value, with an initval of
        the maximum value (4294967295)."
    ::= { testTimeTicks 5 }

testTimeTicksMaxPlusOneInitval OBJECT-TYPE
    SYNTAX      TimeTicks
    MAX-ACCESS  read-write
    STATUS      current
    DESCRIPTION
        "A read-write, unsigned, 32-bits integer value, with an initval of
        the maximum value (4294967295) plus one."
    ::= { testTimeTicks 6 }

testTimeTicksReadOnly OBJECT-TYPE
    SYNTAX      TimeTicks
    MAX-ACCESS  read-only
    STATUS      current
    DESCRIPTION
        "A read-only, unsigned, 32-bits integer value, with no initval."
    ::= { testTimeTicks 7 }

-- Test OIDs for the IpAddress scalar type
testIpAddressNoInitval OBJECT-TYPE
    SYNTAX      IpAddress
    MAX-ACCESS  read-write
    STATUS      current
    DESCRIPTION
        "A read-write IpAddress with no initval."
    ::= { testIpAddress 1 }

testIpAddressEmptyInitval OBJECT-TYPE
    SYNTAX      IpAddress
    MAX-ACCESS  read-write
    STATUS      current
    DESCRIPTION
        "A read-write IpAddress with an empty string as initval."
    ::= { testIpAddress 2 }

testIpAddress1234Initval OBJECT-TYPE
    SYNTAX      IpAddress
    MAX-ACCESS  read-write
    STATUS      current
    DESCRIPTION
        "A read-write IpAddress with an '1.2.3.4' string as initval."
    ::= { testIpAddress 3 }

-- Test OIDs for the TruthValue scalar type
testTruthValueNoInitval OBJECT-TYPE
    SYNTAX      TruthValue
    MAX-ACCESS  read-write
    STATUS      current
    DESCRIPTION
        "A TruthValue with no initval."
    ::= { testTruthValue 1 }

testTruthValueTrueInitval OBJECT-TYPE
    SYNTAX      TruthValue
    MAX-ACCESS  read-write
    STATUS      current
    DESCRIPTION
        "A TruthValue with an initval of True."
    ::= { testTruthValue 2 }

testTruthValueFalseInitval OBJECT-TYPE
    SYNTAX      TruthValue
    MAX-ACCESS  read-write
    STATUS      current
    DESCRIPTION
        "A TruthValue with an initval of False."
    ::= { testTruthValue 3 }

-- Test OIDs for the Float scalar type
testFloatNoInitval OBJECT-TYPE
    SYNTAX      Float
    MAX-ACCESS  read-write
    STATUS      current
    DESCRIPTION
        "A read-write, signed, 32-bits IEEE 754 float value, with no initval."
    ::= { testFloat 1 }

testFloatZeroPointZeroInitval OBJECT-TYPE
    SYNTAX      Float
    MAX-ACCESS  read-write
    STATUS      current
    DESCRIPTION
        "A read-write, signed, 32-bits IEEE 754 float value, with an initval of
        0.0."
    ::= { testFloat 2 }

testFloatZeroPointOneInitval OBJECT-TYPE
    SYNTAX      Float
    MAX-ACCESS  read-write
    STATUS      current
    DESCRIPTION
        "A read-write, signed, 32-bits IEEE 754 float value, with an initval of
        0.1."
    ::= { testFloat 3 }

testFloatOnePointTwoInitval OBJECT-TYPE
    SYNTAX      Float
    MAX-ACCESS  read-write
    STATUS      current
    DESCRIPTION
        "A read-write, signed, 32-bits IEEE 754 float value, with an initval of
        1.2."
    ::= { testFloat 4 }

testFloatMinusZeroPointOneInitval OBJECT-TYPE
    SYNTAX      Float
    MAX-ACCESS  read-write
    STATUS      current
    DESCRIPTION
        "A read-write, signed, 32-bits IEEE 754 float value, with an initval of
        -0.1"
    ::= { testFloat 5 }

testFloatMinusOnePointTwoInitval OBJECT-TYPE
    SYNTAX      Float
    MAX-ACCESS  read-write
    STATUS      current
    DESCRIPTION
        "A read-write, signed, 32-bits IEEE 754 float value, with an initval of
        -1.2"
    ::= { testFloat 6 }

-- Test OIDs for the OctetString scalar type
testOctetStringNoInitval OBJECT-TYPE
    SYNTAX      OctetString
    MAX-ACCESS  read-write
    STATUS      current
    DESCRIPTION
        "A read-write OctetString with no initval."
    ::= { testOctetString 1 }

testOctetStringEmptyInitval OBJECT-TYPE
    SYNTAX      OctetString
    MAX-ACCESS  read-write
    STATUS      current
    DESCRIPTION
        "A read-write OctetString with an empty string as initval."
    ::= { testOctetString 2 }

testOctetStringOneASCIICharInitval OBJECT-TYPE
    SYNTAX      OctetString
    MAX-ACCESS  read-write
    STATUS      current
    DESCRIPTION
        "A read-write OctetString with a string consisting of a single
        ASCII character as initval."
    ::= { testOctetString 3 }

testOctetStringOneUTF8CharInitval OBJECT-TYPE
    SYNTAX      OctetString
    MAX-ACCESS  read-write
    STATUS      current
    DESCRIPTION
        "A read-write OctetString with a string consisting of a single
        UTF8 character as initval."
    ::= { testOctetString 4 }

testOctetString255ASCIICharsInitval OBJECT-TYPE
    SYNTAX      OctetString
    MAX-ACCESS  read-write
    STATUS      current
    DESCRIPTION
        "A read-write OctetString with a string consisting of 255 ASCII
        characters as initval."
    ::= { testOctetString 5 }

testOctetString255UTF8CharsInitval OBJECT-TYPE
    SYNTAX      OctetString
    MAX-ACCESS  read-write
    STATUS      current
    DESCRIPTION
        "A read-write OctetString with a string consisting of 255 UTF8
        characters as initval."
    ::= { testOctetString 6 }

testOctetString256ASCIICharsInitval OBJECT-TYPE
    SYNTAX      OctetString
    MAX-ACCESS  read-write
    STATUS      current
    DESCRIPTION
        "A read-write OctetString with a string consisting of 256 ASCII
        characters as initval."
    ::= { testOctetString 7 }

testOctetString256UTF8CharsInitval OBJECT-TYPE
    SYNTAX      OctetString
    MAX-ACCESS  read-write
    STATUS      current
    DESCRIPTION
        "A read-write OctetString with a string consisting of 256 UTF8
        characters as initval."
    ::= { testOctetString 8 }

-- Test OIDs for the DisplayString scalar type
testDisplayStringNoInitval OBJECT-TYPE
    SYNTAX      DisplayString
    MAX-ACCESS  read-write
    STATUS      current
    DESCRIPTION
        "A read-write DisplayString with no initval."
    ::= { testDisplayString 1 }

testDisplayStringEmptyInitval OBJECT-TYPE
    SYNTAX      DisplayString
    MAX-ACCESS  read-write
    STATUS      current
    DESCRIPTION
        "A read-write DisplayString with an empty string as initval."
    ::= { testDisplayString 2 }

testDisplayStringOneASCIICharInitval OBJECT-TYPE
    SYNTAX      DisplayString
    MAX-ACCESS  read-write
    STATUS      current
    DESCRIPTION
        "A read-write DisplayString with a string consisting of a single
        ASCII character as initval."
    ::= { testDisplayString 3 }

testDisplayString255ASCIICharsInitval OBJECT-TYPE
    SYNTAX      DisplayString
    MAX-ACCESS  read-write
    STATUS      current
    DESCRIPTION
        "A read-write DisplayString with a string consisting of 255 ASCII
        characters as initval."
    ::= { testDisplayString 4 }

testDisplayString256ASCIICharsInitval OBJECT-TYPE
    SYNTAX      DisplayString
    MAX-ACCESS  read-write
    STATUS      current
    DESCRIPTION
        "A read-write DisplayString with a string consisting of 256 ASCII
        characters as initval."
    ::= { testDisplayString 5 }

END
